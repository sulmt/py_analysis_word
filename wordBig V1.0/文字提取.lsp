(defun c:rr (/ elist1 en1 faith-ssget file1 lst1 ss1 str1)
	(vl-load-com)
	(progn
		(defun Faith-ssget (msg / ss1)
			(princ msg)
			(setvar "NOMUTT" 1)
			(setq ss1 (vl-catch-all-apply 'ssget '(":e:s" ((0 . "text")))))
			(setvar "NOMUTT" 0)
			ss1
		)
	)
	(foreach x '("图号" "图名" "测区名称" "比例尺")
		(while (not (setq ss1 (Faith-ssget (strcat "\n请选择" x ",按esc退出:")))))
		(if (vl-catch-all-error-p ss1)
			(quit)
			(progn
				(setq en1 (ssname ss1 0)
					elist1 (entget en1)
					str1 (cdr (assoc 1 elist1))
					lst1 (cons str1 lst1)
				)
			)
		)
	)
	(setq file1 (open "D:/工作/word操作.txt" "w"))
	(foreach x (reverse lst1)
		(write-line x file1)
	)
	(close file1)
  	(princ)
  	(princ "**************************successful!!!************************")
	(princ)
)
(princ "\n功能:文字提取。命令:rr。作者:zuishuaiqiu")
(princ)
